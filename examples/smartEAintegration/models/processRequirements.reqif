# Specification: Specification Document
- Description: Requirements Document

## R1 (Requirement Type)
Cancellation of a reservation must be mailed using  public key cryptography

## R4 (Requirement Type)
Store encrypted credit card data associated with customer account for recurring payments

## R5 (Requirement Type)
Update customer transaction record

## R2

## R3 (Requirement Type)
