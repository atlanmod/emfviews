# Specification: Specification Document
- Description: Requirements Document

## R1
Controller filter requests

## R4
Controller extracts data

## R5
Controller map requests to commands

## R6
Controller invokes command to request

## R2
Controller validates captchas

## R7
View determines the page to display

## R3
View formats the page to display

## R8
Model retrieves data from database
